FME workspace Lire_Interlis1_Ecrire_Interlis2_BF.fmw

Parameters:
- SourceDataset_ch.ehi.fme.Main_7 = P:\Geodonnees\Formation\Formation_MGDM_interlis\Exercice_MO_BF_PF\Donnees_Interlis1\150Rivaz_BF.itf   # Original INTERLIS 2 File
- SourceDataset_ch.ehi.fme.Main = P:\Geodonnees\Formation\Formation_MGDM_interlis\Exercice_MO_BF_PF\Donnees_Interlis1\150Rivaz_BF.itf   # Original INTERLIS 2 File
- DestDataset_ch.ehi.fme.Main_2 = P:\Geodonnees\Formation\Formation_MGDM_interlis\Exercice_MO_BF_PF\Fichier_xtf\Bien_fonds.xtf   # Destination INTERLIS File
- SourceDataset_ch.ehi.fme.Main_6 = P:\Geodonnees\Formation\Formation_MGDM_interlis\Exercice_MO_BF_PF\Donnees_Interlis1\150Rivaz_BF.itf   # Original INTERLIS 2 File
- SourceDataset_ch.ehi.fme.Main_5 = P:\Geodonnees\Formation\Formation_MGDM_interlis\Exercice_MO_BF_PF\Donnees_Interlis1\150Rivaz_BF.itf   # Original INTERLIS 2 File

Readers:
- ch.ehi.fme.Main_1: ch.ehi.fme.Main from $(SourceDataset_ch.ehi.fme.Main_7)
- ch.ehi.fme.Main_2: ch.ehi.fme.Main from $(SourceDataset_ch.ehi.fme.Main)
- ch.ehi.fme.Main_3: ch.ehi.fme.Main from $(SourceDataset_ch.ehi.fme.Main_5)
- ch.ehi.fme.Main_4: ch.ehi.fme.Main from $(SourceDataset_ch.ehi.fme.Main_6)

Writers:
- ch.ehi.fme.Main_5: ch.ehi.fme.Main to $(DestDataset_ch.ehi.fme.Main_2)

Bookmark: Couches BF au format "itf"
Note: Classe "Bien_fonds. / PosImmeuble" / au format "itf"
MD01MOCH24MN95F.Biens_fonds.PosImmeuble (reader ch.ehi.fme.Main_4)
    attributes: xtf_id xtf_char(200), PosImmeuble_de xtf_char(200), Ori xtf_decimal(5,1), HAli xtf_char(255), VAli xtf_char(255), Grandeur xtf_char(255), Ligne_auxiliaire xtf_buffer
    -> AttributeRenamer_3
Note: Classe "Bien_fonds. / Point_limite" / au format "itf"
MD01MOCH24MN95F.Biens_fonds.Point_limite (reader ch.ehi.fme.Main_4)
    attributes: xtf_id xtf_char(200), Origine xtf_char(200), Identification xtf_char(12), PrecPlan xtf_decimal(5,1), FiabPlan xtf_char(255), Signe xtf_char(255), Defini_exactement xtf_char(255), Anc_borne_speciale xtf_char(255)
    -> AttributeRenamer_2
Note: Classe "Bien_fonds. / Mise_a_jourBF" / au format "itf"
MD01MOCH24MN95F.Biens_fonds.Mise_a_jourBF (reader ch.ehi.fme.Main_3)
    attributes: xtf_id xtf_char(200), IdentDN xtf_char(12), Identification xtf_char(12), Description xtf_char(30), Validite xtf_char(255), En_vigueur xtf_date, Enregistrement_RF xtf_date, Date1 xtf_date, Date2 xtf_date
    -> AttributeRenamer
Note: Classe "Bien_fonds. / Immeuble" / au format "itf"
MD01MOCH24MN95F.Biens_fonds.Immeuble (reader ch.ehi.fme.Main_1)
    attributes: xtf_id xtf_char(200), Origine xtf_char(200), IdentDN xtf_char(12), Numero xtf_char(12), EGRIS_EGRID xtf_char(14), Validite xtf_char(255), Integralite xtf_char(255), Genre xtf_char(255), Superficie_totale xtf_int32
    -> Tester_2
Note: Classe "Bien_fonds. / Bien_fonds" / au format "itf"
MD01MOCH24MN95F.Biens_fonds.Bien_fonds (reader ch.ehi.fme.Main_1)
    attributes: xtf_id xtf_char(200), Bien_fonds_de xtf_char(200), PartieNumeroImmeuble xtf_char(12), Superficie xtf_int32
    -> UUIDGenerator_2
Note: Classe "Bien_fonds. / Mise_a_jour_ / Geometrie_LT" / au format "itf"
MD01MOCH24MN95F.Biens_fonds.Bien_fonds_Geometrie_LT (reader ch.ehi.fme.Main_2)
    attributes: xtf_id xtf_char(200), Genre_ligne xtf_char(255)
    -> Tester_5

Bookmark: Création de la classe "GrundstueckPos" au format "xtf"
Note: Renommage de xtf_id
AttributeRenamer_3
    ATTR_TABLE = RENAME_SET_DEFAULT xtf_id > xtf_id_origine_PosImm
    -> UUIDGenerator_7
Note: Création de UUID
UUIDGenerator_7
    UUID_ATTR = xtf_id_PosImm
    -> StringReplacer_4
Note: moyenne -> durchschnittliche
StringReplacer_4
    NO_MATCH = _FME_NO_OP_
    CASE = NO
    REPLACE_TEXT = durchschnittliche
    SRC_ATTRS = Grandeur
    REGEXP = NO
    FIND_TEXT = moyenne
    -> AttributeCreator_14
Note: Merge = 1 pour faire la / jointure qui suit
AttributeCreator_14
    ATTR_TABLE = SET_TO Merge = 1
    -> FeatureMerger_9 [REQUESTOR]
Note: Pour joindre le UUID / du "xtf_basket"
FeatureMerger_9
    MERGE_TYPE = Attributes Only
    SUPPLIERS_FIRST = No
    ATTR_ACCUM_MODE = Merge Supplier
    REJECT_NULL_MISSING_KEYS = No
    ATTR_CONFLICT_RES = Use Requestor
    PROCESS_DUPS = No
    JOIN_KEYS = @Value(Merge) @Value(Merge) AUTO
    IGNORE_NULLS = No
    MERGED -> AttributeCreator_15
Note: Création de la classe / "GrundstueckPos"
AttributeCreator_15
    ATTR_LIST = xtf_class,DM_Flex_AV_CH_LS_V1_0.Liegenschaften.GrundstueckPos,xtf_basket,@Value(xtf_id_Baskets)
    -> FeatureMerger_10 [REQUESTOR]
Note: Pour joindre la clé / externe "PosImmeuble_de"
FeatureMerger_10
    MERGE_TYPE = Attributes Only
    SUPPLIERS_FIRST = No
    ATTR_ACCUM_MODE = Merge Supplier
    REJECT_NULL_MISSING_KEYS = No
    ATTR_CONFLICT_RES = Use Requestor
    PROCESS_DUPS = No
    JOIN_KEYS = @Value(PosImmeuble_de) @Value(xtf_id_Immeuble) AUTO
    IGNORE_NULLS = No
    MERGED -> GeometryExtractor_3
Note: Pour extraie la géométrie / de type ponctuelle (3D)
GeometryExtractor_3
    OGCVERSION = 1.2
    KIND_LONG = FME Binary
    OGC_WKT_PRECISION_DISPLAY = Shortened 64-bit
    PREFER_POLYGON_OVER_SURFACE = No
    REMOVE_GEOMETRY = No
    OGEOSMS_URL_PREFIX = http://maps.google.com/?q=
    ATTR = Pos
    -> 3DForcer
Note: Pour forcer une / géométrie 3D
3DForcer
    KEEPZVAL = No
    ZVALATTR = 0
    -> DM_Flex_AV_CH_LS_V1_0.Liegenschaften.GrundstueckPos (writer ch.ehi.fme.Main_5)
Note: Classe "GrundstueckPos" / au format "xtf"
DM_Flex_AV_CH_LS_V1_0.Liegenschaften.GrundstueckPos (writer ch.ehi.fme.Main_5)
    attributes: xtf_id xtf_char(36), Pos xtf_buffer, Ori xtf_number(5,1), HAli xtf_char(20), VAli xtf_char(20), Groesse xtf_char(50), Hilfslinie xtf_buffer, GrundstueckPos_Von xtf_char(36)

Bookmark: Création de la classe "Grenzpunkt" au format "xtf"
Note: Renommage de xtf_id
AttributeRenamer_2
    ATTR_TABLE = RENAME_SET_DEFAULT xtf_id > xtf_id_origine_PL
    -> UUIDGenerator_5
Note: Création de UUID
UUIDGenerator_5
    UUID_ATTR = xtf_id_PL
    -> StringReplacer_2
Note: oui -> ja
StringReplacer_2
    NO_MATCH = _FME_NO_OP_
    CASE = NO
    REPLACE_TEXT = ja
    SRC_ATTRS = Anc_borne_speciale,Defini_exactement,FiabPlan
    REGEXP = NO
    FIND_TEXT = oui
    -> StringReplacer_3
Note: non -> nein
StringReplacer_3
    NO_MATCH = _FME_NO_OP_
    CASE = NO
    REPLACE_TEXT = nein
    SRC_ATTRS = Anc_borne_speciale,Defini_exactement,FiabPlan
    REGEXP = NO
    FIND_TEXT = non
    -> ExpressionEvaluator
Note: "PrecPlan" de mètres / à centimètres
ExpressionEvaluator
    ACTION = Create New Attribute
    VAL_ATTR = PrecPlan
    EXPRESSION = @Value(PrecPlan)/100
    -> AttributeRounder
Note: "PrecPlan" avec 3 / cases décimales
AttributeRounder
    ROUND_TYPE = Nearest
    SRC_ATTRS = PrecPlan
    PLACES = 3
    -> AttributeValueMapper_4
Note: Mapping Français -> Allemand / de plusieurs attributs
AttributeValueMapper_4
    DIRECTION = Forward (Source To Destination)
    LUT = borne,Stein,cheville,Bolzen,croix,Kreuz,non_materialise,unversichert,pieu,Pfahl
    VAL_ATTR = Signe
    SRC = Signe
    -> AttributeCreator_12
Note: Merge = 1 pour faire la / jointure qui suit
AttributeCreator_12
    ATTR_TABLE = SET_TO Merge = 1
    -> FeatureMerger_7 [REQUESTOR]
Note: Pour joindre le UUID / du "xtf_basket"
FeatureMerger_7
    MERGE_TYPE = Attributes Only
    SUPPLIERS_FIRST = No
    ATTR_ACCUM_MODE = Merge Supplier
    REJECT_NULL_MISSING_KEYS = No
    ATTR_CONFLICT_RES = Use Requestor
    PROCESS_DUPS = No
    JOIN_KEYS = @Value(Merge) @Value(Merge) AUTO
    IGNORE_NULLS = No
    MERGED -> AttributeCreator_13
Note: Création de la classe / "Grenzpuntk"
AttributeCreator_13
    ATTR_LIST = xtf_class,DM_Flex_AV_CH_LS_V1_0.Liegenschaften.Grenzpunkt,xtf_basket,@Value(xtf_id_Baskets)
    -> FeatureMerger_8 [REQUESTOR]
Note: Pour joindre la clé / externe "Origine"
FeatureMerger_8
    MERGE_TYPE = Attributes Only
    SUPPLIERS_FIRST = No
    ATTR_ACCUM_MODE = Merge Supplier
    REJECT_NULL_MISSING_KEYS = No
    ATTR_CONFLICT_RES = Use Requestor
    PROCESS_DUPS = No
    JOIN_KEYS = @Value(Origine) @Value(xtf_id_origine_BF) AUTO
    IGNORE_NULLS = No
    MERGED -> DM_Flex_AV_CH_LS_V1_0.Liegenschaften.Grenzpunkt (writer ch.ehi.fme.Main_5)
Note: Classe "Grenzpunkt" / au format "xtf"
DM_Flex_AV_CH_LS_V1_0.Liegenschaften.Grenzpunkt (writer ch.ehi.fme.Main_5)
    attributes: xtf_id xtf_char(36), Identifikator xtf_char(12), LageGen xtf_number(10,3), LageZuv xtf_boolean, Punktzeichen xtf_char(50), ExaktDefiniert xtf_boolean, HoheitsgrenzsteinAlt xtf_boolean, Entstehung xtf_char(36)

Bookmark: Création de la classe "LSNachfuehrung" au format "xtf"
Note: Renommage de xtf_id
AttributeRenamer
    ATTR_TABLE = RENAME_SET_DEFAULT xtf_id > xtf_id_origine_BF
    -> UUIDGenerator_4
Note: Création de UUID
UUIDGenerator_4
    UUID_ATTR = xtf_id_MAJBF
    -> AttributeCreator_4
Note: Merge = 1 pour faire la / jointure qui suit et création / d'autres attributs
AttributeCreator_4
    ATTR_TABLE:
      SET_TO Gueltigkeit = gueltig
      SET_TO Merge = 1
      SET_TO GBEintrag = 20190328
    -> FeatureMerger_5 [REQUESTOR]
Note: Pour joindre le UUID / du "xtf_basket"
FeatureMerger_5
    MERGE_TYPE = Attributes Only
    SUPPLIERS_FIRST = No
    ATTR_ACCUM_MODE = Merge Supplier
    REJECT_NULL_MISSING_KEYS = No
    ATTR_CONFLICT_RES = Use Requestor
    PROCESS_DUPS = No
    JOIN_KEYS = @Value(Merge) @Value(Merge) AUTO
    IGNORE_NULLS = No
    MERGED -> FeatureMerger_6 [SUPPLIER]
    MERGED -> AttributeCreator_8
    MERGED -> FeatureMerger_8 [SUPPLIER]
Note: Création de la classe / "LSNachfuehrung"
AttributeCreator_8
    ATTR_LIST = xtf_class,DM_Flex_AV_CH_LS_V1_0.Liegenschaften.LSNachfuehrung,xtf_basket,@Value(xtf_id_Baskets)
    -> GeometryExtractor_2
Note: Pour extraie la géométrie / de type surfacique
GeometryExtractor_2
    OGCVERSION = 1.2
    KIND_LONG = FME Binary
    OGC_WKT_PRECISION_DISPLAY = Shortened 64-bit
    PREFER_POLYGON_OVER_SURFACE = No
    REMOVE_GEOMETRY = No
    OGEOSMS_URL_PREFIX = http://maps.google.com/?q=
    ATTR = Perimeter
    -> Tester_3
Note: Tester "En vigueur" / = "null"
Tester_3
    TEST_DESCRIPTION = ""
    BOOL_OP = OR
    TEST_MODE = Automatic
    TEST_CLAUSE = TEST En_vigueur ATTRIBUTE_IS_MISSING ""
    PASSED -> AttributeCreator_10
    FAILED -> DateTimeConverter
Note: "En vigueur" / = "28032019"
AttributeCreator_10
    ATTR_TABLE = SET_TO En_vigueur = 20190328
    -> DateTimeConverter
Note: Attributs "En_vigueur" / et "GBEintrag"au format / "DateTime"
DateTimeConverter
    OUT_FORMAT = ISO
    DATETIME_ATTR = En_vigueur GBEintrag
    REPAIR_INPUT = NO
    -> StringConcatenator
Note: Attribut "En vigueur" / concatenant "DateTime" / et "T00:00:00.000"
StringConcatenator
    ATTRLIST = En_vigueur
    PARM_LINE = @Value(En_vigueur)T00:00:00.000
    ACTION = Overwrite Existing Attributes
    -> StringConcatenator_2
Note: Attribut "GBEintrag" / concatenant "DateTime" / et "T00:00:00.000"
StringConcatenator_2
    ATTRLIST = GBEintrag
    PARM_LINE = @Value(GBEintrag)T00:00:00.000
    ACTION = Overwrite Existing Attributes
    -> DM_Flex_AV_CH_LS_V1_0.Liegenschaften.LSNachfuehrung (writer ch.ehi.fme.Main_5)
Note: Classe "LSNachfuehrung" / au format "xtf"
DM_Flex_AV_CH_LS_V1_0.Liegenschaften.LSNachfuehrung (writer ch.ehi.fme.Main_5)
    attributes: xtf_id xtf_char(36), NBIdent xtf_char(12), Identifikator xtf_char(12), Beschreibung xtf_char(30), Gueltigkeit xtf_char(200), GueltigerEintrag xtf_datetime, GBEintrag xtf_datetime, Perimeter xtf_buffer

Bookmark: Création de la classe "Gruendstuck" au format "xtf"
Note: Sélection de "bien_fonds"
Tester_2
    TEST_DESCRIPTION = ""
    BOOL_OP = OR
    TEST_MODE = Automatic
    TEST_CLAUSE = TEST @Value(Genre) = bien_fonds
    PASSED -> UUIDGenerator
Note: Création de UUID
UUIDGenerator
    UUID_ATTR = xtf_id_gruend
    -> AttributeValueMapper
    -> AttributeRenamer_4
Note: Renommage de / l'attribut "xtf_id"
AttributeRenamer_4
    ATTR_TABLE = RENAME_SET_DEFAULT xtf_id > xtf_id_Immeuble
    -> FeatureMerger_10 [SUPPLIER]
Note: Mapping Français -> Allemand / de plusieurs attributs
AttributeValueMapper
    DIRECTION = Forward (Source To Destination)
    LUT = bien_fonds,Liegenschaft,DDP.superficie,SelbstRecht.Baurecht
    VAL_ATTR = Genre
    SRC = Genre
    -> AttributeValueMapper_2
Note: "en_vigueur" -> / "rechtskraeftig"
AttributeValueMapper_2
    DIRECTION = Forward (Source To Destination)
    LUT = en_vigueur,rechtskraeftig
    VAL_ATTR = Validite
    SRC = Validite
    -> AttributeValueMapper_3
Note: "complet" -> / "Vollstaendig"
AttributeValueMapper_3
    DIRECTION = Forward (Source To Destination)
    LUT = complet,Vollstaendig
    VAL_ATTR = Integralite
    SRC = Integralite
    -> AttributeCreator_7
Note: Merge = 1 pour faire la / jointure qui suit et création / d'autres attributs
AttributeCreator_7
    ATTR_TABLE = SET_TO Merge = 1
    -> FeatureMerger_2 [REQUESTOR]
Note: Pour joindre le UUID / du "xtf_basket"
FeatureMerger_2
    MERGE_TYPE = Attributes Only
    SUPPLIERS_FIRST = No
    ATTR_ACCUM_MODE = Merge Supplier
    REJECT_NULL_MISSING_KEYS = No
    ATTR_CONFLICT_RES = Use Requestor
    PROCESS_DUPS = No
    JOIN_KEYS = @Value(Merge) @Value(Merge) AUTO
    IGNORE_NULLS = No
    MERGED -> AttributeCreator
Note: Création de la classe / "Grundstueck"
AttributeCreator
    ATTR_LIST = xtf_class,DM_Flex_AV_CH_LS_V1_0.Liegenschaften.Grundstueck,xtf_basket,@Value(xtf_id_Baskets)
    -> FeatureMerger_4 [SUPPLIER]
    -> FeatureMerger_6 [REQUESTOR]
Note: Pour joindre la clé / externe "Origine"
FeatureMerger_6
    MERGE_TYPE = Attributes Only
    SUPPLIERS_FIRST = No
    ATTR_ACCUM_MODE = Merge Supplier
    REJECT_NULL_MISSING_KEYS = No
    ATTR_CONFLICT_RES = Use Requestor
    PROCESS_DUPS = No
    JOIN_KEYS = @Value(Origine) @Value(xtf_id_origine_BF) AUTO
    IGNORE_NULLS = No
    MERGED -> DM_Flex_AV_CH_LS_V1_0.Liegenschaften.Grundstueck (writer ch.ehi.fme.Main_5)
Note: Classe "Grundstueck" / au format "xtf"
DM_Flex_AV_CH_LS_V1_0.Liegenschaften.Grundstueck (writer ch.ehi.fme.Main_5)
    attributes: xtf_id xtf_char(36), NBIdent xtf_char(12), Nummer xtf_char(12), EGRIS_EGRID xtf_char(14), Gueltigkeit xtf_char(255), Vollstaendigkeit xtf_char(255), Art xtf_char(255), GesamteFlaechenmass xtf_int32, Entstehung xtf_char(36), Loeschung xtf_char(36)

Bookmark: Création de la classe "Liegenschaft" au format "xtf"
Note: Création de UUID
UUIDGenerator_2
    UUID_ATTR = xtf_id
    -> FeatureMerger [REQUESTOR]
    -> Chopper
Note: Transformation d'objets / surfaciques en objets linéaires / (plsuieurs lignes)
Chopper
    MAX_VERTICES = 2
    REMNANT_ATTR = _remnant
    CHOPPED_ATTR = _chopped
    MODE = By Vertex
    -> SpatialFilter [Candidate]
Note: Sélection d'une ligne / entre deux bien fonds
Tester_5
    TEST_DESCRIPTION = ""
    BOOL_OP = OR
    TEST_MODE = Automatic
    TEST_CLAUSE = TEST @Value(xtf_id) = 14677623
    PASSED -> Chopper_2
Note: Transformation de la / ligne en plusieurs lignes
Chopper_2
    MAX_VERTICES = 2
    REMNANT_ATTR = _remnant
    CHOPPED_ATTR = _chopped
    MODE = By Vertex
    -> SpatialFilter [Filter]
Note: Filtre spatial ("equals") pour / sélection du "xtf_id" du bien fond
SpatialFilter
    PREDATTR = _predicate
    PREDICATE_VALUE = Equals
    CURVE_BOUNDARY_RULE_PARAM = Default Rule
    PASS_CRITERIA = Pass Against One Filter
    MERGE_ATTRS = Yes
    BASE_TYPE = Multiple Filters
    USE_BOUNDING_BOX = No
    PASSED -> AttributeCreator_5
Note: Pour joindre les multignes (lignes de conflit) / aux objets surfaciques (bein fonds)
FeatureMerger
    SUPPLIER_PREFIX_DUMMY = YES
    IGNORE_NULLS = Yes
    MERGE_TYPE = Attributes Only
    SUPPLIERS_FIRST = No
    PROCESS_DUPS = No
    JOIN_KEYS = @Value(xtf_id) @Value(xtf_id) AUTO
    MERGED -> AttributeCreator_9
    NOT_MERGED -> AttributeCreator_9
Note: Merge = 1 pour faire la / jointure qui suit et création / d'autres attributs
AttributeCreator_9
    ATTR_TABLE = SET_TO Merge = 1
    -> FeatureMerger_3 [REQUESTOR]
Note: Pour joindre le UUID / du "xtf_basket"
FeatureMerger_3
    MERGE_TYPE = Attributes Only
    SUPPLIERS_FIRST = No
    ATTR_ACCUM_MODE = Merge Supplier
    REJECT_NULL_MISSING_KEYS = No
    ATTR_CONFLICT_RES = Use Requestor
    PROCESS_DUPS = No
    JOIN_KEYS = @Value(Merge) @Value(Merge) AUTO
    IGNORE_NULLS = No
    MERGED -> AttributeCreator_3
Note: Création de la classe / "Liegenschaft"
AttributeCreator_3
    ATTR_LIST = xtf_class,DM_Flex_AV_CH_LS_V1_0.Liegenschaften.Liegenschaft,xtf_basket,@Value(xtf_id_Baskets)
    -> FeatureMerger_4 [REQUESTOR]
Note: Pour joindre la clé / externe "Bien_fonds_de"
FeatureMerger_4
    MERGE_TYPE = Attributes Only
    SUPPLIERS_FIRST = No
    ATTR_ACCUM_MODE = Merge Supplier
    REJECT_NULL_MISSING_KEYS = No
    ATTR_CONFLICT_RES = Use Requestor
    PROCESS_DUPS = No
    JOIN_KEYS = @Value(Bien_fonds_de) @Value(xtf_id) AUTO
    IGNORE_NULLS = No
    MERGED -> DM_Flex_AV_CH_LS_V1_0.Liegenschaften.Liegenschaft (writer ch.ehi.fme.Main_5)
Note: Classe "Liegenschaft" / au format "xtf"
DM_Flex_AV_CH_LS_V1_0.Liegenschaften.Liegenschaft (writer ch.ehi.fme.Main_5)
    attributes: xtf_id xtf_char(36), Liegenschaft_von xtf_char(36), NummerTeilGrundstueck xtf_char(12), Flaechenmass xtf_int32, Streitig{}.Lines{}.xtf_class xtf_char(200), Streitig{}.Lines{}.Line xtf_buffer, Streitig{}.xtf_class xtf_char(200)

Bookmark: Attribut "Streitig" : Géométrie de type "MultiLigne"
Note: Création de la classe / "GeometryCHLV95_V1.LineStructure"
AttributeCreator_5
    ATTR_LIST = xtf_class,GeometryCHLV95_V1.LineStructure
    -> GeometryExtractor
Note: Pour extraie la géométrie / de type ligne
GeometryExtractor
    KIND_LONG = FME Binary
    ATTR = Line
    -> ListBuilder
Note: Création de liste pour stockage des / géométries de type "ligne"
ListBuilder
    GRP_BY = xtf_id
    LIST_NAME = Lines
    -> AttributeCreator_6
Note: Création de la classe / "GeometryCHLV95_V1.MultiLine"
AttributeCreator_6
    ATTR_LIST = xtf_class,GeometryCHLV95_V1.MultiLine
    -> ListBuilder_2
Note: Création de liste pour stockage des / géométries de type "multiligne"
ListBuilder_2
    GRP_BY = xtf_id
    LIST_NAME = Streitig
    -> FeatureMerger [SUPPLIER]

Bookmark: BF_topic
Creator
    GEOMTYPE = Geometry Object
    NUM = 1
    CREATED -> UUIDGenerator_3
Note: Création de UUID
UUIDGenerator_3
    UUID_ATTR = xtf_id_Baskets
    -> AttributeCreator_2
Note: Création de TOPIC
AttributeCreator_2
    ATTR_LIST = xtf_id,@Value(xtf_id_Baskets),xtf_topic,DM_Flex_AV_CH_LS_V1_0.Liegenschaften,Merge,1
    -> XTF_BASKETS (writer ch.ehi.fme.Main_5)
    -> FeatureMerger_2 [SUPPLIER]
    -> FeatureMerger_3 [SUPPLIER]
    -> FeatureMerger_5 [SUPPLIER]
    -> FeatureMerger_7 [SUPPLIER]
    -> FeatureMerger_9 [SUPPLIER]
XTF_BASKETS (writer ch.ehi.fme.Main_5)
    attributes: xtf_topic xtf_char(200), xtf_id xtf_char(200)
