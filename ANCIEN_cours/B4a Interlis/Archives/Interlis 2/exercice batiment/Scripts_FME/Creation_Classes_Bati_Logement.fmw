FME workspace Creation_Classes_Bati_Logement.fmw

Parameters:
- SourceDataset_SHAPE = P:\Geodonnees\Formation\Formation_MGDM_interlis\Shapes\Batiments.shp   # Source Esri Shape File(s)
- DestDataset_SHAPE = P:\Geodonnees\Formation\Formation_MGDM_interlis\Shapes   # Destination Esri Shape Folder
- DestDataset_CSV = P:\Geodonnees\Formation\Formation_MGDM_interlis\Shapes   # Destination CSV (CommaSeparatedValue) Folder

Readers:
- SHAPE_1: SHAPE from $(SourceDataset_SHAPE)

Writers:
- SHAPE_2: SHAPE to $(DestDataset_SHAPE)
- CSV_1: CSV to $(DestDataset_CSV)

Batiments (reader SHAPE_1)
    attributes: OBJECTID number(10,0), ID number(10,0), QUALITE number(10,0), QUALITE_TX char(5), GENRE number(10,0), GENRE_TXT char(50), NUMERO char(12), REGBL_EGID number(10,0), DESIGNATIO number(10,0), DESIGNAT_1 char(30), IDENTDN char(12), SHAPE_AREA number(19,11), SHAPE_LEN number(19,11)
    -> Counter
Counter
    SCOPE = Global
    START = 1
    DOMAIN = counter
    CNT_ATTR = Bati_ID
    -> AttributeKeeper
AttributeKeeper
    KEEP_ATTRS = Bati_ID
    -> RandomNumberGenerator
RandomNumberGenerator
    MIN = 1
    MAX = 3
    PLACES = 0
    RESULT_ATTR = _random_number
    -> AttributeValueMapper
AttributeValueMapper
    VAL_ATTR = _looked_up
    DIRECTION = Forward (Source To Destination)
    LUT = 1,En_projet,2,Construit,3,Demoli
    SRC = _random_number
    -> AttributeRenamer
AttributeRenamer
    ATTR_LIST = _looked_up,StatutBati,
    -> Bati (writer SHAPE_2)
Bati (writer SHAPE_2)
    attributes: Bati_ID char(200), StatutBati char(200)
Creator
    NUM = 50
    GEOMTYPE = Geometry Object
    CREATED -> RandomNumberGenerator_2
RandomNumberGenerator_2
    MIN = 1
    MAX = 20
    PLACES = 0
    RESULT_ATTR = Bati_Avec
    -> RandomNumberGenerator_3
RandomNumberGenerator_3
    MIN = 10
    MAX = 100
    PLACES = 2
    RESULT_ATTR = Surface
    -> Logements (writer CSV_1)
Logements (writer CSV_1)
    attributes: Bati_Avec number(10,0), Surface number(10,2)
