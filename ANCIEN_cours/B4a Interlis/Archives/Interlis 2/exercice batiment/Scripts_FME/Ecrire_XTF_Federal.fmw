FME workspace Ecrire_XTF_Federal.fmw

Parameters:
- SourceDataset_SHAPE = P:\Geodonnees\Formation\Formation_MGDM_interlis\MGDM_Bati_Logement\Donnees\Bati_Shape\Bati.shp   # Source Esri Shape File(s)
- SourceDataset_CSV = P:\Geodonnees\Formation\Formation_MGDM_interlis\MGDM_Bati_Logement\Donnees\Logements_CSV\Logements.csv   # Source CSV (CommaSeparatedValue) File(s)
- DestDataset_ch.ehi.fme.Main = P:\Geodonnees\Formation\Formation_MGDM_interlis\MGDM_Bati_Logement\Fichier_XTF\Bati_Logements_Federal.xtf   # Destination INTERLIS File

Readers:
- SHAPE_1: SHAPE from $(SourceDataset_SHAPE)
- CSV_1: CSV from $(SourceDataset_CSV)

Writers:
- ch.ehi.fme.Main_1: ch.ehi.fme.Main to $(DestDataset_ch.ehi.fme.Main)

Bati (reader SHAPE_1)
    attributes: Bati_ID char(200), StatutBati char(200)
    -> AttributeRenamer_2
AttributeRenamer_2
    ATTR_LIST = Bati_ID,Bati,
    -> CenterPointReplacer
    -> Counter_3
CenterPointReplacer
    CENTERPOINT -> Counter_2
Counter_2
    CNT_ATTR = xtf_id
    DOMAIN = counter
    SCOPE = Global
    START = 1
    -> AttributeCreator_3
AttributeCreator_3
    ATTR_LIST = xtf_class,BatiFederal.Bati.BatimentCentroide,xtf_basket,b1
    -> BatiFederal.Bati.BatimentCentroide (writer ch.ehi.fme.Main_1)
BatiFederal.Bati.BatimentCentroide (writer ch.ehi.fme.Main_1)
    attributes: xtf_id xtf_char(200), StatutBati xtf_char(200), Bati xtf_number(20,0)
Counter_3
    CNT_ATTR = xtf_id
    DOMAIN = counter
    SCOPE = Global
    START = 1
    -> AttributeCreator_4
AttributeCreator_4
    ATTR_LIST = xtf_class,BatiFederal.Bati.BatimentPolygone,xtf_basket,b1
    -> BatiFederal.Bati.BatimentPolygone (writer ch.ehi.fme.Main_1)
BatiFederal.Bati.BatimentPolygone (writer ch.ehi.fme.Main_1)
    attributes: xtf_id xtf_char(200), StatutBati xtf_char(200), Bati xtf_number(20,0)
CSV (reader CSV_1)
    attributes: col0 number(3,0), col1 number(5,2)
    -> AttributeRenamer
AttributeRenamer
    ATTR_LIST = col0,Bati_Avec,,col1,Surface,
    -> Counter_4
Counter_4
    CNT_ATTR = xtf_id
    DOMAIN = counter
    SCOPE = Global
    START = 1
    -> AttributeCreator_5
AttributeCreator_5
    ATTR_LIST = xtf_class,BatiFederal.Bati.Logement,xtf_basket,b1
    -> BatiFederal.Bati.Logement (writer ch.ehi.fme.Main_1)
BatiFederal.Bati.Logement (writer ch.ehi.fme.Main_1)
    attributes: xtf_id xtf_char(200), Surface xtf_number(10,2), Bati_Avec xtf_number(10,0)

Bookmark: bati_logements_xtf_basket_topic
Creator
    GEOMTYPE = Geometry Object
    NUM = 1
    CREATED -> AttributeCreator_2
AttributeCreator_2
    ATTR_LIST = xtf_id,b1,xtf_topic,BatiFederal.Bati
    -> XTF_BASKETS (writer ch.ehi.fme.Main_1)
XTF_BASKETS (writer ch.ehi.fme.Main_1)
    attributes: xtf_topic xtf_char(74), xtf_id xtf_char(200)
